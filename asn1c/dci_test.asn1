DCIReportModule DEFINITIONS ::= BEGIN

DCIReport ::= SEQUENCE 
{
    metadataheader  MetaDataHeader
}

MetaDataHeader ::= SEQUENCE
{
    version                 INTEGER (0..255),
    numinfometaheader       NumInfoMetaHeaderStructure,
    skip0                   INTEGER (0..255)
}

NumInfoMetaHeaderStructure ::= SEQUENCE
{
    duplexmode              DuplexMode,
    skip1                   INTEGER (0..15),
    numofrecords            INTEGER (0..31),
    subframecfg             INTEGER (0..15),
    skip2                   INTEGER (0..3)
}

DuplexMode ::= ENUMERATED
{
    fdd     (0),
    unknown (1)
}

RecordHeader ::= SEQUENCE
{
    skip3                   BIT STRING(SIZE (8)),
    skip4                   INTEGER(0..7),
    tpcdcirntitype          TpcDciRntiType,
    numdlgrant              INTEGER(0..7),
    numulgrant              INTEGER(0..7),
    subframenumber          INTEGER(0..15),
    systemframenumber       INTEGER(0..1023)
}

TpcDciRntiType ::= ENUMERATED
{
    crnti      (0),
    unknown     (1)
}

DCIUL ::= SEQUENCE
{
    kofdci0                  BIT STRING(SIZE (3)),
    ulinedxdai               BIT STRING(SIZE (3)),
    cellIndex                CELLINDEX,
    tpc                      BIT STRING(SIZE (2)),
    harqid                   BIT STRING(SIZE (3)),
    ndi                      BIT STRING(SIZE (1)),
    rntitype                 BIT STRING(SIZE (3)),

    tbsindex                 BIT STRING(SIZE (6)),
    mcsindex                 BIT STRING(SIZE (5)),
    redundancyversionindex   BIT STRING(SIZE (2)),
    skip5                    BIT STRING(SIZE (3)),

    resourceallocationtype   BIT STRING(SIZE (1)),
    srsquest                 SRSQUEST,
    cqirequest               BIT STRING(SIZE (3)),
    modulationtype           ModulationType,

    numberofresourceblocks   BIT STRING(SIZE (6)),
    startofresourceblock     BIT STRING(SIZE (7)),
    rbgsize                  BIT STRING(SIZE (3)),

    hoppingflag              HOPPINGFLAG,
    searchspace              BIT STRING(SIZE (2)),
    skip6                    BIT STRING(SIZE (1)),
    cyclicshiftdmrs          BIT STRING(SIZE (3)),
    skip7                    BIT STRING(SIZE (1)),

    rivvalue                 BIT STRING(SIZE (12)),
    rivwidth                 BIT STRING(SIZE (4)),

    numberofresourceblocks2  BIT STRING(SIZE (7)),
    startofresourceblock2    BIT STRING(SIZE (7)),
    skip8                    BIT STRING(SIZE (2)),

    skip9                    BIT STRING(SIZE (3)),
    aggregationlevel         BIT STRING(SIZE (2)),
    skip10                   BIT STRING(SIZE (3)),

    skip11                   OCTET STRING (SIZE (3))
}

CELLINDEX ::= ENUMERATED
{
    pcc        (0),
    unknown     (1)
}
SRSQUEST ::= ENUMERATED
{
    no          (0),
    unknown     (1)
}
ModulationType ::= ENUMERATED
{
    unknown0    (0),
    unknown1    (1),
    i16qam       (2),
    i64qam       (3),
    unknown4    (4),
    unknown5    (5),
    unknown6    (6),
    unknown7    (7)
}
HOPPINGFLAG ::= ENUMERATED
{
    disabled    (0),
    unknown     (1)
}

DCIDL ::= SEQUENCE
{
    rntitype            RntiType,
    dlggregationlevel   BIT STRING(SIZE (1)),
    dlsearchspace       BIT STRING(SIZE (1)),
    dldai               BIT STRING(SIZE (1)),
    skip12              BIT STRING(SIZE (1)),
    dlgranttpccmd       BIT STRING(SIZE (2)),
    numacknackbits      BIT STRING(SIZE (2)),
    dlgrantformattype   DlGrantFormatType,
    skip13              BIT STRING(SIZE (2)),
    dlgrantcellindex    DlGrantCellIndex,
    
    dlgrantncce         INTEGER(0..255),
    skip14              OCTET STRING (SIZE (5))
}
RntiType ::= ENUMERATED
{
    crnti      (0),
    unknown     (1)
}
DlGrantFormatType ::= ENUMERATED
{
    type1a     (0),
    type2      (1),
    unknown    (2),
    unknown1    (3)
}
DlGrantCellIndex ::= ENUMERATED
{
    pcc        (0),
    scc1        (1),
    scc2        (2),
    unkown3      (3),
    unkown4      (4),
    unkown5      (5),
    unkown6      (6),
    unkown7      (7)
}
END
